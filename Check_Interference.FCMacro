# FreeCAD Macro
# -*- coding: utf-8 -*-
# Copyright (c) 2024 John Hyslop
# License: Free to use; use at your own risk.
#
# This macro is provided "as is," without warranty of any kind, express or implied.
# The user assumes all responsibility for the use of this macro.
#
# Description:
# This macro checks for interferences between selected bodies in the active FreeCAD document.
# It analyses the geometry of the selected objects to determine if they intersect or overlap.
# If any interferences are detected, a message box will display the results, 
# informing the user of the specific bodies involved. 
# This tool is especially useful for assembly validation and ensuring proper clearances
# in complex models.
#
# Version: 1.0
# Date: 04/11/2024
# Changelog:
# - [Version 1.0] Initial release
# - [Future changes or versions will be noted here]

import FreeCAD
import FreeCADGui
from PySide import QtGui
from itertools import combinations

def is_valid_shape(obj):
    """Check if the object is a valid shape."""
    return hasattr(obj, 'Shape') and obj.Shape.isValid()

def show_message(title, message):
    """Show a message box with a given title and message."""
    msg_box = QtGui.QMessageBox()
    msg_box.setWindowTitle(title)
    msg_box.setText(message)
    msg_box.setStandardButtons(QtGui.QMessageBox.Ok)
    msg_box.exec_()

def analyse_interference(selected_objects):
    """Analyse interferences between selected shapes."""
    selected_shapes = [obj for obj in selected_objects if is_valid_shape(obj)]
    
    if len(selected_shapes) < 2:
        show_message("Invalid Selection", "No valid shapes selected. Please select at least 2 parts or shapes.")
        return

    interference_names = []
    
    for shape1, shape2 in combinations(selected_shapes, 2):
        intersection = shape1.Shape.common(shape2.Shape)
        if intersection.isValid() and not intersection.isNull():
            # Check if the intersection has a volume or area to determine if it's empty
            if intersection.Volume > 0 or intersection.Area > 0:
                interference_body = FreeCAD.ActiveDocument.addObject("Part::Feature", f"Interference_{shape1.Name}_{shape2.Name}")
                interference_body.Shape = intersection
                
                # Set colour to bright red and transparency
                interference_body.ViewObject.ShapeColor = (1.0, 0.0, 0.0)  # Red colour
                interference_body.ViewObject.Transparency = 50  # Set to 50% transparency
                
                interference_names.append(interference_body.Name)

    if interference_names:
        FreeCAD.ActiveDocument.recompute()  # Recompute the active document
        message = f"Created the following interferences:\n" + "\n".join(interference_names) + \
                  "\nPlease inspect these interferences before deleting them."
        show_message("Interference Created", message)
    else:
        show_message("Result", "No interferences detected.")

# Main execution
if __name__ == "__main__":
    selected_objects = FreeCADGui.Selection.getSelection()
    analyse_interference(selected_objects)
